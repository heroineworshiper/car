#  create sections for the remote charger

import libisogrid
import libclamshell
import importlib
importlib.reload(libclamshell)
importlib.reload(libisogrid)
import math


BORDER = 1.0
CLAMSHELL = 'clamshell'
ISOGRID_H = 3.6
if True:
    extrudeTris, extrudeSubs = libisogrid.makeGrid(55, \
        111, \
        4, \
        6, \
        [ BORDER, BORDER ], \
        [ BORDER, BORDER ], \
        0.0, \
        0.0, \
        ISOGRID_H, \
        BORDER)
    extrudeTris.Placement = App.Placement(
        App.Vector(-29.00, 54.50, -19.60),
        App.Rotation(App.Vector(0, 0, 1), 0))

if False:
# isogrid outline & cropping tool
    libisogrid.cropBorder('outline', \
        None, \
        0, \
        0, \
        0, \
        BORDER, \
        ISOGRID_H, \
        math.pi / 2,
        None,
        True,
        True)



# clamshell walls
if False:
    libclamshell.makeClam(libclamshell.getObj(CLAMSHELL), 
        9.2 / 2, 
        0, 
        math.pi / 2,
        True)
