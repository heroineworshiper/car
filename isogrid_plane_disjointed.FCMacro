# create an isogrid plane



import FreeCAD
import Sketcher
import math

# wide wall
#W = 89.4
#H = 66.0
#X_SLICES = 5
#Y_SLICES = 3
#Y_BORDER = 2
#X_BORDER = 2


# narrow wall
W = 71.0
H = 66.0
X_SLICES = 4
Y_SLICES = 3
Y_BORDER = 2
X_BORDER = 4


# multiple of line width
RIB_WIDTH = 1.2
# smaller ribs
RIB_WIDTH2 = 0.8


SLICE_H = (H - Y_BORDER * 2) / Y_SLICES
SLICE_W = (W - X_BORDER * 2) / X_SLICES


doc = App.activeDocument()


def toRad(angle):
    return angle * math.pi * 2.0 / 360.0

# make a closed polygon
def makePoly(sketch, coords):
    for i in range(0, len(coords) - 1):
        sketch.addGeometry(Part.LineSegment(coords[i],
            coords[i + 1]),
            False)
    sketch.addGeometry(Part.LineSegment(coords[len(coords) - 1],
        coords[0]),
        False)
        
    

# make an iso triangle
def makeTri(sketch, 
    sketch2,
    corners, 
    innerCorners,
    x1, 
    x2, 
    y1, 
    y2, 
    y3,
    flipX):

    innerCorners2 = []
    corners2 = []
# defeat call by reference
    for i in range(0, 3):
        innerCorners2.append(
            App.Vector(innerCorners[i].x, innerCorners[i].y, 0.0))
    
    for i in range(0, 6):
        corners2.append(
            App.Vector(corners[i].x, corners[i].y, 0.0))


    if flipX:
        x3 = x2
        x2 = x1
        x1 = x3
        for i in range(0, 3):
            innerCorners2[i].x *= -1

        for i in range(0, 6):
            corners2[i].x *= -1


    coords = [
        App.Vector(x1, y1, 0.0) + corners2[1],
        App.Vector(x1, y3, 0.0) + corners2[5],
        App.Vector(x2, y2, 0.0) + corners2[3]]
    makePoly(sketch, coords)

# inner subdivisions
    center_x = x1 + (x2 - x1) / 2 / 1.732
    x_offset = (corners2[5].x - corners2[0].x) / 2 + innerCorners2[2].x / 2
    y_offset = (corners2[5].y - corners2[0].y) / 2 + innerCorners2[2].y / 2
    coords = [
    # left
        App.Vector(x1 + corners2[1].x, y2 + innerCorners2[1].y, 0.0),
    # center
        App.Vector(center_x, y2, 0.0) + innerCorners2[1],
    # top right
        App.Vector((x1 + x2) / 2 + x_offset, (y2 + y3) / 2 + y_offset, 0.0) + innerCorners2[1],
        App.Vector((x1 + x2) / 2 + x_offset, (y2 + y3) / 2 + y_offset, 0.0) + innerCorners2[0],
    # center
        App.Vector(center_x, y2, 0.0) + innerCorners2[0],
    # bottom right
        App.Vector((x1 + x2) / 2 + x_offset, (y1 + y2) / 2 - y_offset, 0.0) + innerCorners2[0],
        App.Vector((x1 + x2) / 2 + x_offset, (y1 + y2) / 2 - y_offset, 0.0) + innerCorners2[2],
    # center
        App.Vector(center_x, y2, 0.0) + innerCorners2[2],
    # left
        App.Vector(x1 + corners2[1].x, y2 - innerCorners2[1].y, 0.0),
        ]
    makePoly(sketch2, coords)





def makeGrid():
    sketch = doc.addObject('Sketcher::SketchObject','gridsketch')
    sketch2 = doc.addObject('Sketcher::SketchObject','gridsketch')

# radius of the circle joining 6 ribs
    radius = RIB_WIDTH
# offsets of the 6 triangle corners around each center coordinate
# coordinates are counterclockwise
    corners = []
    for i in range(0, 6):
        corner = App.Vector( \
            radius * math.cos(toRad(i * 60)), \
            radius * math.sin(toRad(i * 60)), \
            0.0)
        corners.append(corner)

# offsets of the 3 inner triangle corners
    innerCorners = []
    innerRadius = RIB_WIDTH2 / 1.732
    
    
#    print('makeGrid innerRadius=', innerRadius)
    for i in range(0, 3):
        corner = App.Vector( \
            innerRadius * math.cos(toRad(i * 120)), \
            innerRadius * math.sin(toRad(i * 120)), \
            0.0)
        innerCorners.append(corner)

# bottom & top row
    for x in range(0, X_SLICES):
        center_x1 = X_BORDER + x * SLICE_W
        center_x2 = X_BORDER + (x + 1) * SLICE_W
        if (x % 2) == 0:
# bottom left
            center_y1 = Y_BORDER
            center_y2 = Y_BORDER + .5 * SLICE_H
            coords = [
                App.Vector(center_x1, center_y1, 0.0) + App.Vector(corners[0].x, 0, 0),
                App.Vector(center_x2, center_y1, 0.0) + App.Vector(corners[4].x, 0, 0),
                App.Vector(center_x2, center_y2, 0.0) + corners[4]]
            makePoly(sketch, coords)

# top left
            center_y2 = Y_BORDER + Y_SLICES * SLICE_H
            center_y1 = Y_BORDER + (Y_SLICES - .5) * SLICE_H
            coords = [
                App.Vector(center_x1, center_y2, 0.0) + App.Vector(corners[0].x, 0, 0),
                App.Vector(center_x2, center_y2, 0.0) + App.Vector(corners[4].x, 0, 0),
                App.Vector(center_x2, center_y1, 0.0) + corners[2]]
            makePoly(sketch, coords)
        else:
# bottom right
            center_y1 = Y_BORDER
            center_y2 = Y_BORDER + .5 * SLICE_H
            coords = [
                App.Vector(center_x2, center_y1, 0.0) + App.Vector(corners[3].x, 0, 0),
                App.Vector(center_x1, center_y1, 0.0) + App.Vector(corners[1].x, 0, 0),
                App.Vector(center_x1, center_y2, 0.0) + corners[5]]
            makePoly(sketch, coords)
# top right
            center_y2 = Y_BORDER + Y_SLICES * SLICE_H
            center_y1 = Y_BORDER + (Y_SLICES - .5) * SLICE_H
            coords = [
                App.Vector(center_x2, center_y2, 0.0) + App.Vector(corners[3].x, 0, 0),
                App.Vector(center_x1, center_y2, 0.0) + App.Vector(corners[1].x, 0, 0),
                App.Vector(center_x1, center_y1, 0.0) + corners[1]]
            makePoly(sketch, coords)

        
        
# middle rows
    for y in range(0, Y_SLICES):
        for x in range(0, X_SLICES):
            center_y1 = Y_BORDER + y * SLICE_H
            center_y2 = Y_BORDER + (y + .5) * SLICE_H
            center_y3 = Y_BORDER + (y + 1) * SLICE_H
            center_x1 = X_BORDER + x * SLICE_W
            center_x2 = X_BORDER + (x + 1) * SLICE_W

# debug
#            coords = [
#                App.Vector(center_x1, center_y1, 0.0) + corners[0],
#                App.Vector(center_x1, center_y1, 0.0) + corners[1],
#                App.Vector(center_x1, center_y1, 0.0) + corners[2],
#                App.Vector(center_x1, center_y1, 0.0) + corners[3],
#                App.Vector(center_x1, center_y1, 0.0) + corners[4],
#                App.Vector(center_x1, center_y1, 0.0) + corners[5]
#            ]
#            makePoly(sketch, coords)
#
#            coords = [
#                App.Vector(center_x1, center_y1, 0.0) + innerCorners[0],
#                App.Vector(center_x1, center_y1, 0.0) + innerCorners[1],
#                App.Vector(center_x1, center_y1, 0.0) + innerCorners[2]
#            ]
#            makePoly(sketch, coords)

            makeTri(sketch, 
                sketch2,
                corners, 
                innerCorners,
                center_x1, 
                center_x2, 
                center_y1, 
                center_y2, 
                center_y3,
                (x % 2) != 0)

            if y < Y_SLICES - 1:
                center_y1 += SLICE_H / 2
                center_y2 += SLICE_H / 2
                center_y3 += SLICE_H / 2

                makeTri(sketch, 
                    sketch2,
                    corners, 
                    innerCorners,
                    center_x1, 
                    center_x2, 
                    center_y1, 
                    center_y2, 
                    center_y3,
                    (x % 2) == 0)




# border
    coords = [
        App.Vector(0.0, 0.0, 0.0),
        App.Vector(0.0, H, 0.0),
        App.Vector(W, H, 0.0),
        App.Vector(W, 0.0, 0.0),
        ]
    makePoly(sketch, coords)

    extrude1 = doc.addObject('Part::Extrusion', 'gridextrude')
    extrude1.Base = sketch
    extrude1.DirMode = "Normal"
    extrude1.DirLink = None
    extrude1.LengthFwd = 2.000000000000000
    extrude1.LengthRev = 0.000000000000000
    extrude1.Solid = True
    extrude1.Reversed = False
    extrude1.Symmetric = False
    extrude1.TaperAngle = 0.000000000000000
    f.TaperAngleRev = 0.000000000000000

    extrude2 = doc.addObject('Part::Extrusion', 'gridextrude')
    extrude2.Base = sketch2
    extrude2.DirMode = "Normal"
    extrude2.DirLink = None
    extrude2.LengthFwd = 1.000000000000000
    extrude2.LengthRev = 0.000000000000000
    extrude2.Solid = True
    extrude2.Reversed = False
    extrude2.Symmetric = False
    extrude2.TaperAngle = 0.000000000000000
    f.TaperAngleRev = 0.000000000000000
    fusion = doc.addObject("Part::MultiFuse","grid")
    fusion.Shapes = [extrude1, extrude2]


    doc.recompute()



makeGrid()
