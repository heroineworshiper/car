# honeycomb tire with flat smooth tread & .4mm line width
# helix.c or helix.py is required to extrude the tread

import FreeCAD
import Sketcher
import Draft
import math


SKETCH_Z = 0.0

doc = App.activeDocument()
gui = Gui.activeDocument()

def extruderDefaults(x):
    x.DirMode = "Normal"
    x.DirLink = None
    x.LengthFwd = 0.0
    x.LengthRev = 0.0
    x.Solid = True
    x.Reversed = False
    x.Symmetric = False
    x.TaperAngle = 0.000000000000000
    x.TaperAngleRev = 0.000000000000000

def toRad(angle):
    return angle * math.pi * 2.0 / 360.0

def toDeg(x):
    return x * 360.0 / 2 / math.pi

def polarToXYZ(angle, radius, z):
    x = radius * math.cos(angle)
    y = -radius * math.sin(angle)
    return App.Vector(x, y, z)

def polarToXYZ2(point):
    angle = point.x
    radius = point.y
    z = point.z
    return polarToXYZ(angle, radius, z)

def XYZToPolar(xyz):
    fraction = xyz.z / LENGTH
    aspect = (TOP_ASPECT * fraction) + (1.0 - fraction)
    xyz.x = xyz.x / aspect
    angle = math.atan2(-xyz.y, xyz.x)
    radius = math.hypot(xyz.x, xyz.y)
    return App.Vector(angle, radius, xyz.z)


# add vector with length & angle to start 
def addLine(start, angle, length):
    result = FreeCAD.Vector(start.x + length * math.cos(angle),
        start.y + length * math.sin(angle),
        start.z)
    return result


def angleChange(old_angle, new_angle):
    result = new_angle - old_angle
    if result > math.pi: 
        result -= math.pi * 2
    elif result < -math.pi:
        result += math.pi * 2
    return result


# make a closed polygon
def makePoly(sketch, coords):
    for i in range(0, len(coords) - 1):
        #print('makePoly ', coords[i], coords[i + 1])
        sketch.addGeometry(Part.LineSegment(coords[i],
            coords[i + 1]),
            False)
    sketch.addGeometry(Part.LineSegment(coords[len(coords) - 1],
        coords[0]),
        False)


# create a border of a certain thickness for the closed polygon
def border(sketch, coords, thickness, borderDirection):
    total = len(coords)
    prevStart = coords[total - 1]
    prevEnd = coords[0]
    start = coords[0]
    end = coords[1]

    borderLine = []

    for i in range(0, total):
        prevAngle = math.atan2(prevEnd.y - prevStart.y, prevEnd.x - prevStart.x)
        nextAngle = math.atan2(end.y - start.y, end.x - start.x)
        angle2 = prevAngle + angleChange(prevAngle, nextAngle) / 2.0 + borderDirection
        mag = abs(1.0 / math.cos(angleChange(prevAngle, nextAngle) / 2.0))
        borderLine.append(addLine(start, angle2, mag * thickness))

        prevStart = start
        prevEnd = end
        start = end
        if i == total - 2:
            end = coords[0]
        elif i == total - 1:
            end = coords[1]
        else:
            end = coords[i + 2]
    makePoly(sketch, borderLine)

def getAngles(column, columns):
# angle range of the column
    angle0 = column * 2 * math.pi / columns
    angle1 = (column + .5) * 2 * math.pi / columns
    angle2 = (column + 1) * 2 * math.pi / columns

# angle of the zigzag points
    angleOffset = 2.0 * math.pi / columns / 8

# angle of outer zigzag points & tread is slightly tweeked to make the tread 50%
# of the circumference
    angleOffset2 = math.pi / columns / 8
    return (angle0, angle1, angle2, angleOffset, angleOffset2)


def makeTire(iRadius, 
    oRadius, 
    iThickness, 
    oThickness,
    layers, # layers of hexagons in a column
    columns, # number of hexagon columns in a layer.  Each column is 2 hexagons side by side
    wallThickness, # thickness of hexagon wall
    tread): # add tread if nonzero

    iDiameter = iRadius * 2
    oDiameter = oRadius * 2

    haveTread = False
    if tread > 0.01:
        haveTread = True

    z = 0.0

    sketch = doc.addObject('Sketcher::SketchObject','tiresketch')
    sketch.Placement = App.Placement(
        App.Vector(0.0, 0.0, z),
        App.Rotation(App.Vector(0, 0, 1), 0.0))
#    gui.getObject(sketch.Label).Visibility = False

# hexagon range of radii
    iRadius = iRadius + iThickness - wallThickness / 2
    oRadius = oRadius - oThickness + wallThickness / 2

    for column in range(0, columns):
        angle0, angle1, angle2, angleOffset, angleOffset2 = getAngles(column, columns)

        layers_i = int(layers)
        if layers > layers_i:
            layers_i = layers_i + 1
        for layer in range(0, layers_i):
            outerLayer = False
            if layer == layers - 1:
                outerLayer = True

# hexagon radius
            r1 = iRadius + layer * (oRadius - iRadius) / layers
            r2 = iRadius + (layer + .5) * (oRadius - iRadius) / layers
            r3 = iRadius + (layer + 1) * (oRadius - iRadius) / layers
            r4 = iRadius + (layer + 1.5) * (oRadius - iRadius) / layers

#            print('angle0=', angle0, ' angle1=', angle1, ' r1=', r1, ' r2=', r2, ' angleOffset=', angleOffset)
# full hexagon, even column
            if outerLayer:
                subdivisions = 2
                coords = []
                angle3 = angle1 - angleOffset
                angle4 = angle0 + angleOffset
                for i in range(subdivisions + 1):
                    coords.append(polarToXYZ(angle3 + i * (angle4 - angle3) / subdivisions, r1, 0.0))
                coords.append(polarToXYZ(angle0 - angleOffset, r2, 0.0))
                
                angle3 = angle0 + angleOffset
                angle4 = angle1 - angleOffset
                for i in range(subdivisions + 1):
                    coords.append(polarToXYZ(angle3 + i * (angle4 - angle3) / subdivisions, r3, 0.0))
                coords.append(polarToXYZ(angle1 + angleOffset, r2, 0.0))
                border(sketch, coords, wallThickness / 2, -math.pi / 2)

            else:
# inner full hexagon, even column
# clamp radius in case of a fractional layer
                if r3 > oRadius:
                    r3 = oRadius
                    coords = [
                        polarToXYZ(angle0 + angleOffset, r1, 0.0),
                        polarToXYZ(angle0 - angleOffset2, r2, 0.0),
                        polarToXYZ(angle0 + angleOffset, r3, 0.0),
                        polarToXYZ(angle1 - angleOffset, r3, 0.0),
                        polarToXYZ(angle1 + angleOffset2, r2, 0.0),
                        polarToXYZ(angle1 - angleOffset, r1, 0.0)
                    ]
                else:
                    coords = [
                        polarToXYZ(angle0 + angleOffset, r1, 0.0),
                        polarToXYZ(angle0 - angleOffset, r2, 0.0),
                        polarToXYZ(angle0 + angleOffset, r3, 0.0),
                        polarToXYZ(angle1 - angleOffset, r3, 0.0),
                        polarToXYZ(angle1 + angleOffset, r2, 0.0),
                        polarToXYZ(angle1 - angleOffset, r1, 0.0)
                    ]
                border(sketch, coords, wallThickness / 2, -math.pi / 2)

            if layer == 0:
# inner hexagon, odd column
                coords = []
                angle3 = angle2 + angleOffset
                angle4 = angle1 - angleOffset
                subdivisions = 4
                for i in range(subdivisions + 1):
                    coords.append(polarToXYZ(angle3 + i * (angle4 - angle3) / subdivisions, r1, 0.0))
                coords.append(polarToXYZ(angle1 + angleOffset, r2, 0.0))
                coords.append(polarToXYZ(angle2 - angleOffset, r2, 0.0))
                border(sketch, coords, wallThickness / 2, -math.pi / 2)
            
            if outerLayer:
# outer hexagon, odd column
                coords = []
                coords.append(polarToXYZ(angle1 + angleOffset, r2, 0.0))
# subdivide outer curve
                angle3 = angle1 - angleOffset
                angle4 = angle2 + angleOffset
                subdivisions = 4
                for i in range(subdivisions + 1):
                    coords.append(polarToXYZ(angle3 + i * (angle4 - angle3) / subdivisions, r3, 0.0))
                
                coords.append(polarToXYZ(angle2 - angleOffset, r2, 0.0))
                border(sketch, coords, wallThickness / 2, -math.pi / 2)



# middle hexagon, odd column
            if layer < layers - 1:
                coords = [
                    polarToXYZ(angle1 + angleOffset, r2, 0.0),
                    polarToXYZ(angle1 - angleOffset, r3, 0.0),
                    polarToXYZ(angle1 + angleOffset2, r4, 0.0),
                    polarToXYZ(angle2 - angleOffset2, r4, 0.0),
                    polarToXYZ(angle2 + angleOffset, r3, 0.0),
                    polarToXYZ(angle2 - angleOffset, r2, 0.0),
                ]
                border(sketch, coords, wallThickness / 2, -math.pi / 2)

# inner shell
    sketch.addGeometry(Part.Circle(App.Vector(0, 0, 0),
        App.Vector(0, 0, 1),
        iDiameter / 2))

# outer shell
    if not haveTread:
        sketch.addGeometry(Part.Circle(App.Vector(0, 0, 0),
            App.Vector(0, 0, 1),
            oDiameter / 2))
    else:
# tread
        wallAngle = (2 * math.pi) * oThickness / (oDiameter * math.pi)
        for column in range(0, columns):
            angle0, angle1, angle2, angleOffset, angleOffset2 = getAngles(column, columns)

# rotate the tread if a fractional layer
            if (layers % 1) > 0.1:
                treadOffset = math.pi / columns
                angle0 += treadOffset
                angle1 += treadOffset
                angle2 += treadOffset

            angle3 = angle0 + angleOffset2
            angle4 = angle1 - angleOffset2

# even column
            angle5 = angle3 - wallAngle
            angle6 = angle4 + wallAngle
            r5 = oDiameter / 2 + tread - oThickness
            r6 = oDiameter / 2 + tread
            r7 = oRadius + wallThickness / 2
# fillet offsets
            angle3b = angle3 + 1.0 / (r5 - 1)
            angle4b = angle4 - 1.0 / (r5 - 1)
# circumference lines of the tread
            for i in range(subdivisions):
                sketch.addGeometry(Part.LineSegment(
                    polarToXYZ(angle5 + i * (angle6 - angle5) / subdivisions, r6, 0.0),
                    polarToXYZ(angle5 + (i + 1) * (angle6 - angle5) / subdivisions, r6, 0.0)),
                    False)
                sketch.addGeometry(Part.LineSegment(
                    polarToXYZ(angle3b + i * (angle4b - angle3b) / subdivisions, r5, 0.0),
                    polarToXYZ(angle3b + (i + 1) * (angle4b - angle3b) / subdivisions, r5, 0.0)),
                    False)
                sketch.addGeometry(Part.LineSegment(
                    polarToXYZ(angle3 + i * (angle4 - angle3) / subdivisions, r7, 0.0),
                    polarToXYZ(angle3 + (i + 1) * (angle4 - angle3) / subdivisions, r7, 0.0)),
                    False)
# inside fillets
            sketch.addGeometry(Part.LineSegment(
                polarToXYZ(angle3, r5 - 1, 0.0),
                polarToXYZ(angle3b, r5, 0.0)),
                False)
            sketch.addGeometry(Part.LineSegment(
                polarToXYZ(angle4, r5 - 1, 0.0),
                polarToXYZ(angle4b, r5, 0.0)),
                False)
# radial lines of the tread
            sketch.addGeometry(Part.LineSegment(
                    polarToXYZ(angle3, r7, 0.0),
                    polarToXYZ(angle3, r5 - 1, 0.0)),
                    False)
            sketch.addGeometry(Part.LineSegment(
                    polarToXYZ(angle4, r7, 0.0),
                    polarToXYZ(angle4, r5 - 1, 0.0)),
                    False)
            sketch.addGeometry(Part.LineSegment(
                    polarToXYZ(angle5, oDiameter / 2, 0.0),
                    polarToXYZ(angle5, r6, 0.0)),
                    False)
            sketch.addGeometry(Part.LineSegment(
                    polarToXYZ(angle6, oDiameter / 2, 0.0),
                    polarToXYZ(angle6, r6, 0.0)),
                    False)

# odd column.  Section joining the treads
            angle3 = angle1 - angleOffset2
            angle4 = angle2 + angleOffset2
            angle3 += wallAngle
            angle4 -= wallAngle
            for i in range(subdivisions):
                sketch.addGeometry(Part.LineSegment(
                    polarToXYZ(angle3 + i * (angle4 - angle3) / subdivisions, oDiameter / 2, 0.0),
                    polarToXYZ(angle3 + (i + 1) * (angle4 - angle3) / subdivisions, oDiameter / 2, 0.0)),
                    False)



#makeTire(22.0, 54.0 1.0, 1.0, 3, 12, .5, 0)

# PLA core
#makeTire(21.5, 42.7, 1.0, 1.0, 2, 12, .5, 0)

# TPU center
#makeTire( 21.5, 42.5, 1.0, 1.0, 2, 12, 1.0, 0)


# 74mm TPU tire
#makeTire(26.0, 37.0, .5, 1.0, 1, 12, .5, 0)

# 74mm PLA core
#makeTire(21.5, 25.5, .5, 1.0, 1, 18, .5, 0)

# 108mm TPU tire 11mm thick
#makeTire(43.0, 54.0, .5, 1.0, 1, 18, .5, 0)

# 108mm diameter 15mm thick hex TPU
#makeTire(39.0, 54.0, .5, 1.0, 1.5, 18, .5, 0)

# 108mm diameter 10mm thick hex + 5mm thick tread TPU
# Freecad can't make it helical, so you have to extrude, export as STL &
# rotate all Z over 30 in the STL file.
#makeTire(39.0, 49.0, .5, 1.0, 1.0, 18, .5, 5)






# 108mm Onroad PLA core
#makeTire(21.5, 38.5, 0.5, 0.5, 1.5, 12, .5, 0)

# 108mm diameter 15mm thick hex TPU Onroad
#makeTire(39.0, 54.0, .5, 1.2, 1.5, 18, .5, 0)


# 108mm diameter 15mm thick hex + 4mm thick tread TPU Off road
#makeTire(35.0, 50.0, .5, 1.0, 1.5, 16, .5, 4)



# 108mm Offroad PLA core
#makeTire(21.5, 34.5, 0.5, 0.5, 1.0, 12, 1.0, 0)

# 108mm Offroad soft TPE
makeTire(35.0, 50.0, .9, 1.5, 1.5, 16, 1.0, 4)
